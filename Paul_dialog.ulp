#usage "<b>Align ULP Dialog</b>\n"
       "<p>"
       "<author>Author: Paul Badger</author>"

// THIS PROGRAM IS PROVIDED AS IS AND WITHOUT WARRANTY OF ANY KIND, EXPRESSED OR IMPLIED

// Revision 1 : 2014.3.30 support@cadsoft.de

string cmd = "";
int Value = 42;
int Wert = 7;
int Val = 0;
string st = "";
int Result = 0;
string msg = "";

string Colors[] = { "red"
                    , "green", "blue", "pink"
                    , "yellow", "cyan", "magenta"
                    , "brown", "white", "black"
                    , "gray", "orange"
                    };

int Selected = 2; // initially selects "blue"

string Text = "example text";

int Lines = 0;

// Checkboxes in Dialog
int increment  = 0;
int distribute = 1;
int vertical   = 0;
int snap  = 0;
int grid = 0;
int align = 0;
int rotate = 1;
int horizontal =1;


//use dlgRadioButton only in dlgGroup!
// Front end for the align ULP
// Paul Badger 2014


Result = dlgDialog("Align ULP Dialog") {
  dlgVBoxLayout {
     dlgStretch(0);
     dlgGroup("Align Options with flags for command line.") {
        dlgStretch(0);
        dlgGridLayout {
            
           dlgCell(1, 1) {  dlgCheckBox("&Snap to Grid -s", snap); };
           dlgCell(2, 1) {  dlgCheckBox("&Force To Grid -f", grid); };
           dlgCell(3, 1) {  dlgCheckBox("&Force Horizontal -h", horizontal); };
           dlgCell(4, 1) {  dlgCheckBox("&Force Vertical -v", vertical); };
           dlgCell(5, 1)  dlgRadioButton("&Distribute -d", align);
           dlgCell(6, 1)  dlgRadioButton("&Increment -i", align);
           }
           if (dlgSelectionChanged()){
               if (horizontal == 1){
                 vertical = 0;  // mutally exclusive options
                  dlgMessageBox("vertical set to zero");
                  } 
               if (vertical == 1) horizontal = 0;
           } 

        }
     dlgStretch(0);

      dlgLabel("Increment in mils");
      dlgSpacing(5);
      dlgStretch(0);
      dlgHBoxLayout {
         dlgIntEdit(Value, 0, 10000);
         }
      dlgSpacing(10);

      dlgStretch(1);
      }
     
        dlgHBoxLayout {
          
           dlgStretch(0);
           dlgPushButton("+OK") dlgAccept(1);
           dlgStretch(1);
           
        
           dlgSpacing(20);
           dlgStretch(0);
           dlgPushButton("-CANCEL") dlgReject(-1);
           dlgStretch(1);
           }

   dlgStretch(1);
  };

if (Result == 1){
//tools/align.ulp;    // run the ULP - still need to parse out flags
exit (0);
}
